#!/usr/bin/env python3.7
# -*- coding: utf-8 -*-

""" This file acts as a bootstrapper to load DesignSPHysics from the
    "Mod" folder of the FreeCAD install directory.
"""

import sys
import os

""" Disables some types of FreeCAD warnings """
from PySide6.QtCore import qInstallMessageHandler, QtMsgType
def customMessageHandler(type, context, message):
    if "QWindowsWindow::setMouseGrabEnabled" not in message:
        print(message)
qInstallMessageHandler(customMessageHandler)
os.environ["QT_LOGGING_RULES"] = "*.debug=false;*.warning=false"
# --------------------

import logging
class IgnoreMouseGrabWarning(logging.Filter):
    def filter(self, record):
        return "QWindowsWindow::setMouseGrabEnabled" not in record.getMessage()
logger = logging.getLogger()
logger.addFilter(IgnoreMouseGrabWarning)
# --------------------

sys.path.append(os.path.dirname(os.path.abspath(__file__)))
# --------------------

from mod.main import boot  # pylint: disable=wrong-import-position
'''
def report_error(exctype, value, tb):
    """ Displays a dialog with options about the sudden crash. """
    sys.__excepthook__(exctype, value, tb)
    ErrorReportDialog(escape(str(exctype)), escape(str(value)), escape(''.join(format_tb(tb))))'''


#sys.excepthook = report_error
boot()
